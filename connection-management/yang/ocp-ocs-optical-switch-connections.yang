module ocp-ocs-optical-switch-connections {

  yang-version "1";

  // namespace
  namespace "http://openconfig.net/yang/optical-switch-connections";

  prefix "ocp-ocs-opt-sw-conn";

  // imports
  import ietf-yang-types { prefix yang; }
  import openconfig-types { prefix oc-types; }
  import openconfig-yang-types { prefix oc-yang-types; }
  import openconfig-transport-types { prefix oc-opt-types; }
  import openconfig-extensions { prefix oc-ext; }
  import openconfig-platform { prefix oc-platform; }
  import ocp-ocs-optical-switch { prefix ocp-ocs-opt-sw; }

  // meta
  organization "Open Compute Project";

  contact "Me!";

  description
    "This module defines configuration and operational state for the connections in an
     Optical Circuit Switch (OCS).

     Combined with the ocp-ocs-optical-switch and ocp-ocs-optical-switch-port modules,
     functionality is modelled for establishing port connections (cross-connections),
     reporting port statuses, assigning metadata and a variety of other features found
     in OCS products.

     This revision should be considered to be a strawman for further discussion
     within the OCP OCS Subproject.";

  oc-ext:openconfig-version "0.8.0";

  revision "2026-08-28" {
    description "Initial model (strawman based on discussions within the OCP OCS Subproject).";
    reference "0.8.0";
  }

  // OpenConfig specific extensions for module metadata.
  oc-ext:regexp-posix;
  oc-ext:catalog-organization "TBD";
  oc-ext:origin "TBD";

  // identity statements

  // typedef statements

  typedef port-connection-status-enum {
    type enumeration {
      enum CONNECTED {
        description "The connection has successfully been established and the optical path is active.";
      }
      enum PENDING_CONNECTION {
        description "The connection is in the process of being established.";
      }
      enum PENDING_DELETION {
        description "The connection is in the process of being removed.";
      }
      enum FAILED {
        description "The connection has operationally failed but it is still valid intent.";
      }
      enum INVALID {
        description "The connection represents potentially valid intent but cannot be established because
                     of a conflict with other active configuration.";
      }
    }
  }

  typedef ocp-ocs-port-status-enum {
    type enumeration {
      enum BLOCKED {
        description "Port is not in an active connection or is disabled.";
      }
      enum FAILED {
        description "Port has failed and any connections using this port will enter the FAILED state.";
      }
      enum TUNING {
        description "Port is in a transient state in which a connection is being established or deleted.";
      }
      enum TUNED {
        description "Port is in a state where the current intended connection is active.";
      }
      enum UNKNOWN {
        description "Port is in an unknown state.";
      }
    }
  }


  // grouping statements

  grouping port-connection-config {
    description
      "Config data for optical port connections.";

    leaf name {
      type string;
      description "Arbitrary name selected by controller.";
    }
    leaf input-port-name {
      type leafref {
        path "/oc-platform:components/oc-platform:component/oc-platform:name";
      }
      description "Input port for connection.";
    }
    leaf output-port-name {
      type leafref {
        path "/oc-platform:components/oc-platform:component/oc-platform:name";
      }
      description "Output port for connection.";
    }
  }

  grouping port-connection-state {
    description
      "Operational state data for optical port connections.";

    leaf status {
      type port-connection-status-enum;
      description "Port connection status.";
    }
    leaf status-reason {
      type string;
      description "More detailed reason why a connection is FAILED or INVALID";
    }
    leaf last-updated {
      type yang:date-and-time;
      description "Datetime of last status transition for this connection.";
    }
  }

  grouping port-connection-ref {
    description
      "References to the config connection name.";

    leaf name {
      config false;
      type leafref {
        path "../config/name";
      }
      description "The connection name.";
    }
  }

  grouping optical-switch-connections-top {
    description
      "Top-level grouping for optical switch connections.";

    container connections {
      description
        "List of tables for optical switch cross-connections.";

      leaf last-change-time {
        config false;
        type yang:date-and-time;
        description "Datetime of last status transition for this switch/table";
      }
      list port-connection {
        key "name";
        description "List of all defined optical connections in the switch.";

        uses port-connection-ref;

        container config {
          description "Details of connection.";
          uses port-connection-config;
        }

        container state {
          config false;
          uses port-connection-config;
          uses port-connection-state;

          description "Operational state data for optical connections in the switch.";
        }
      }
    }
  }



  // data definition statements

  uses optical-switch-connections-top;

  // augment statements

  // rpc statements

  // notification statements
}
